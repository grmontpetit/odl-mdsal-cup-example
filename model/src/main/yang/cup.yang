module cup {
	yang-version 1;

	namespace
      "http://netconfcentral.org/ns/cup";

    prefix tea;

    organization "Inocybe";

    contact
      "Gabriel Robitaille-Montpetit <grmontpetit@inocybe.com>";

    description
      "YANG version of the TEA-MIB.";

    revision "2014-11-16" {
      description
        "Cup module in progress.";
    }

    identity tea-type {
      description
        "Tea that can be used in the tea cup.";
    }

    identity black-tea {
      base tea:tea-type;
      description "Black tea.";
    }

    identity green-tea {
      base tea-type;
      description "Green tea.";
    }

    identity red-tea {
      base tea-type;
      description "Red tea";
    }

    typedef DisplayString {
      type string {
        length "0 .. 255";
      }
      description
        "YANG version of the SMIv2 DisplayString TEXTUAL-CONVENTION.";
        reference
          "RFC 2579, section 2.";
    }

    container cup {
      presence
        "Indicate that the cup service is available.";
      description
        "Top-level container for all toaster database objects.";

      leaf cupManufacturer {
        type DisplayString;
        config false;
        mandatory true;
        description
          "The name of the cup's manufacturer. For instance China.";
      }

      leaf cupModelNumber {
        type DisplayString;
        config false;
        mandatory true;
        description
          "The name of the cup's model. For instance, yellow cup.";
      }

      leaf cupStatus {
        type enumeration {
          enum "cold" {
            value 1;
            description
              "The water in the cup is cold.";
          }
          enum "heating" {
            value 2;
            description
              "The water is being heated in the microwave.";
          }
        }
        config false;
        mandatory true;
        description
          "This variable indicates the current status of the cup.";
      }
    }// container cup
} // module cup
