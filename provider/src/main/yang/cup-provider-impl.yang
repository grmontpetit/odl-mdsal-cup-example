module cup-provider-impl {
    yang-version 1;
    namespace "urn:opendaylight:params:xml:ns:yang:controller:config:cup-provider:impl";
    prefix "cup-provider-impl";

    import config { prefix config; revision-date 2013-04-05; }
    import opendaylight-md-sal-binding { prefix mdsal; revision-date 2013-10-28; }

    description
        "This module contains the base YANG definitions for cup-provider impl implementation.";

    revision "2014-11-16" {
        description
            "Initial revision.";
    }

    // This is the definition of the service implementation as a module identity
    identity cup-provider-impl {
            base config:module-type;

            // Specifies the prefix for generated java classes.
            config:java-name-prefix CupProvider;
    }

    // Augments the 'configuration' choice node under modules/module.  
    augment "/config:modules/config:module/config:configuration" {
        case cup-provider-impl {
            when "/config:modules/config:module/config:type = 'cup-provider-impl'";

            //wires in the data-broker service 
            container data-broker {
                uses config:service-ref {
                    refine type {
                        mandatory false;
                        config:required-identity mdsal:binding-async-data-broker;
                    }
                }
            }      
        }
    }
}
