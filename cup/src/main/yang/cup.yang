module cup {
    yang-version 1;

    namespace
      "inocybe";

    prefix tea;

    organization "Inocybe";

    contact
      "Gabriel Robitaille-Montpetit <grmontpetit@gmail.com>";

    description
      "YANG version of the TEA-MIB.";

    revision "2014-11-16" {
      description
        "Cup module in progress.";
    }

    identity tea-type {
      description
        "Tea that can be used in the tea cup.";
    }

    identity black-tea {
      base tea:tea-type;
      description "Black tea.";
    }

    identity green-tea {
      base tea-type;
      description "Green tea.";
    }

    identity red-tea {
      base tea-type;
      description "Red tea";
    }

    typedef DisplayString {
      type string {
        length "0 .. 255";
      }
      description
        "YANG version of the SMIv2 DisplayString TEXTUAL-CONVENTION.";
        reference
          "RFC 2579, section 2.";
    }

    container cup {
      presence
        "Indicate that the cup service is available.";
      description
        "Top-level container for all cup database objects.";

      leaf cupManufacturer {
        type DisplayString;
        config false;
        mandatory true;
        description
          "The name of the cup's manufacturer. For instance Acme inc..";
      }

      leaf cupModelNumber {
        type DisplayString;
        config false;
        mandatory true;
        description
          "The name of the cup's model. For instance, yellow cup.";
      }

      leaf cupStatus {
        type enumeration {
          enum "cold" {
            value 0;
            description
              "The water in the cup is cold.";
          }
          enum "heating" {
            value 1;
            description
              "The water is being heated in the microwave.";
          }
        }
        config false;
        mandatory true;
        description
          "This variable indicates the current status of the cup.";
      }
      leaf cupTemperatureFactor {
        type uint32;
        config true;
        default 1000;
        description
          "The cup water temperature factor. Basically, the number of ms to multiple the temperature value by.";
      }

      leaf ammount-of-cups-in-stock {
        type uint32;

        config false;
        default 5;
        description
          "The ammount of cups available.";
      }
      
      leaf ammount-of-cups-made {
        type uint32;
        config false;
        default 0;
        description
          "The ammount of cups that have been made so far.";
      }

    }// container cup
    
    rpc heat-cup {
      description
       "Heat the tea cup in the microwave. The cupHeated notification will be sent when the cup is heated.
        An 'in-use' error will be returned if the cup is already being made. A 'resource-denied' error will 
        be returned if the cup service is disabled.";
      input {
        leaf cupTemperature {
          type uint32 {
            range "75 .. 100";
          }
          default '100';
          description
            "This variable controls the heat of the water. It should be on a scale of 75 to 100.
             Water temperature of 100 is better for black teas and red teas while temperatures
             of 75 are better for green teas.";
         }

        leaf cupTeaType {
          type identityref {
            base tea:tea-type;
          }
          default 'black-tea';
          description
            "This variable informs the cup which tea is beign used. The cup uses this information, 
             combined with cupTemperature, to compute for how long the material must be heated to achieve the required temperature.";
        }
      }// input
    }
    
    // action to cancel making cup - takes no input parameters
    rpc cancel-cup {
      description
        "Stop heating the cup, if any is being made.
          A 'resource-denied' error will be returned 
          if the cup service is disabled.";
    }  // rpc cancel-cup

    rpc restock-cups {
       description
         "Restock the amount of cups with clean cups.";

       input {
           leaf amountOfCupsToClean {
               type uint32;
               description
                 "IndiccupsMadeates the amount of cups to clean.";
           }
       }
    } // restock-cups

    notification noMoreCups {
      description
        "Indicates that there are no available cups to make tea.";
    }  // notification noMoreCups
 
   notification cupsRestocked {
     description
       "Indicates that there are no more cups.";
     leaf amountOfCups {
       type uint32;
       description
         "Indicates the amount of cups that was re-stocked";
     }
   }  // notification cupsRestocked

} // module cup
