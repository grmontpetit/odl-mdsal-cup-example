module cup-provider-impl {

    yang-version 1;
    namespace "urn:opendaylight:params:xml:ns:yang:controller:config:cup-provider:impl";
    prefix "cup-provider-impl";

    import config { prefix config; revision-date 2013-04-05; }
    import rpc-context { prefix rpcx; revision-date 2013-06-17; }
    import opendaylight-md-sal-binding { prefix mdsal; revision-date 2013-10-28; }

    description
        "This module contains the base YANG definitions for cup-provider impl implementation.";

    revision "2014-11-16" {
        description
            "Initial revision.";
    }

    // This is the definition of the service implementation as a module identity
    identity cup-provider-impl {
            base config:module-type;

            // Specifies the prefix for generated java classes.
            config:java-name-prefix CupProvider;
    }

    // Augments the 'configuration' choice node under modules/module.
    augment "/config:modules/config:module/config:configuration" {
        case cup-provider-impl {
            when "/config:modules/config:module/config:type = 'cup-provider-impl'";

            //wires in the data-broker service 
            container broker {
                uses config:service-ref {
                    refine type {
                        mandatory true;
                        config:required-identity mdsal:binding-broker-osgi-registry;
                    }
                }
            }
            // Wires dependent services into this class - in this case the RPC registry service
            // This sub-section register the OpendaylightCup as the Provider for the RPC calls.
            // This section is declaring a dependency on the MD-SAL RPC registry service
            // similiar to the databroker
            container rpc-registry {
                uses config:service-ref {
                    refine type {
                       mandatory true;
                       config:required-identity mdsal:binding-rpc-registry;
                    }
                }
            }
            container notification-service {
               uses config:service-ref {
                  refine type {
                     mandatory true;
                     config:required-identity mdsal:binding-notification-service;
                  }
               }
            }
        }
    }

    // Augment the 'state' choice node under modules/module
    augment "/config:modules/config:module/config:state" {
        case cup-provider-impl {
            when "/config:modules/config:module/config:type = 'cup-provider-impl'";
            leaf cups-made {
                type uint32;
            }
            rpcx:rpc-context-instance "clear-cups-made-rpc";
        }
    }

    identity clear-cups-made-rpc;

    rpc clear-cups-made  {
        description
          "JMX call to clear the cups-made counter.";
        input {
            uses rpcx:rpc-context-ref {
                refine context-instance {
                    rpcx:rpc-context-instance clear-cups-made-rpc;
                }
            }
        }
    }
}
